(defun c:df1 ()
   (setq pt1 (getpoint "\n insertion point"))
   (setq pt2 (getint "\n no. of colum   :  "))
   (setq pt3 (getint "\n no. of foot    :  "))
   (command "insert" "c:\\acad-lib\\civil\\civil\\df1" pt1 1 1 pause ""
            "insert" "c:\\acad-lib\\civil\\civil\\f" pause 1 1 pause pt3 ""
            "insert" "c:\\acad-lib\\civil\\civil\\c" pause 1 1 pause pt2 "")
         )
(defun c:df2 ()
   (setq pt1 (getpoint "\n insertion point"))
   (setq pt2 (getint "\n no. of colum   :  "))
   (setq pt3 (getint "\n no. of foot    :  "))
   (command "insert" "c:\\acad-lib\\civil\\civil\\df2" pt1 1 1 pause ""
            "insert" "c:\\acad-lib\\civil\\civil\\f" pause 1 1 pause pt3 ""
            "insert" "c:\\acad-lib\\civil\\civil\\c" pause 1 1 pause pt2 "")
         )
(defun c:df3 ()
   (setq pt1 (getpoint "\n insertion point"))
   (setq pt2 (getint "\n no. of colum   :  "))
   (setq pt3 (getint "\n no. of foot    :  "))
   (command "insert" "c:\\acad-lib\\civil\\civil\\df3" pt1 1 1 pause ""
            "insert" "c:\\acad-lib\\civil\\civil\\f" pause 1 1 pause pt3 ""
            "insert" "c:\\acad-lib\\civil\\civil\\c" pause 1 1 pause pt2 "")
         )
(defun c:df4 ()
   (setq pt1 (getpoint "\n insertion point"))
   (setq pt2 (getint "\n no. of colum   :  "))
   (setq pt3 (getint "\n no. of foot    :  "))
   (command "insert" "c:\\acad-lib\\civil\\civil\\df4" pt1 1 1 pause ""
            "insert" "c:\\acad-lib\\civil\\civil\\f" pause 1 1 pause pt3 ""
            "insert" "c:\\acad-lib\\civil\\civil\\c" pause 1 1 pause pt2 "")
         )
(defun c:df5 ()
   (setq pt1 (getpoint "\n insertion point"))
   (setq pt2 (getint "\n no. of colum   :  "))
   (setq pt3 (getint "\n no. of foot    :  "))
   (command "insert" "c:\\acad-lib\\civil\\civil\\df5" pt1 1 1 pause ""
            "insert" "c:\\acad-lib\\civil\\civil\\f" pause 1 1 pause pt3 ""
            "insert" "c:\\acad-lib\\civil\\civil\\c" pause 1 1 pause pt2 "")
         )
(defun c:df6 ()
   (setq pt1 (getpoint "\n insertion point"))
   (setq pt2 (getint "\n no. of colum   :  "))
   (setq pt3 (getint "\n no. of foot    :  "))
   (command "insert" "c:\\acad-lib\\civil\\civil\\df6" pt1 1 1 pause ""
            "insert" "c:\\acad-lib\\civil\\civil\\f" pause 1 1 pause pt3 ""
            "insert" "c:\\acad-lib\\civil\\civil\\c" pause 1 1 pause pt2 "")
         )
(defun c:df7 ()
   (setq pt1 (getpoint "\n insertion point"))
   (setq pt2 (getint "\n no. of colum   :  "))
   (setq pt3 (getint "\n no. of foot    :  "))
   (command "insert" "c:\\acad-lib\\civil\\civil\\df7" pt1 1 1 pause ""
            "insert" "c:\\acad-lib\\civil\\civil\\f" pause 1 1 pause pt3 ""
            "insert" "c:\\acad-lib\\civil\\civil\\c" pause 1 1 pause pt2 "")
         )
(defun c:df8 ()
   (setq pt1 (getpoint "\n insertion point"))
   (setq pt2 (getint "\n no. of colum   :  "))
   (setq pt3 (getint "\n no. of foot    :  "))
   (command "insert" "c:\\acad-lib\\civil\\civil\\df8" pt1 1 1 pause ""
            "insert" "c:\\acad-lib\\civil\\civil\\f" pause 1 1 pause pt3 ""
            "insert" "c:\\acad-lib\\civil\\civil\\c" pause 1 1 pause pt2 "")
         )
(defun c:df9 ()
   (setq pt1 (getpoint "\n insertion point"))
   (setq pt2 (getint "\n no. of colum   :  "))
   (setq pt3 (getint "\n no. of foot    :  "))
   (command "insert" "c:\\acad-lib\\civil\\civil\\df9" pt1 1 1 pause ""
            "insert" "c:\\acad-lib\\civil\\civil\\f" pause 1 1 pause pt3 ""
            "insert" "c:\\acad-lib\\civil\\civil\\c" pause 1 1 pause pt2 "")
         )
(defun c:df10 ()
   (setq pt1 (getpoint "\n insertion point"))
   (setq pt2 (getint "\n no. of colum   :  "))
   (setq pt3 (getint "\n no. of foot    :  "))
   (command "insert" "c:\\acad-lib\\civil\\civil\\df10" pt1 1 1 pause ""
            "insert" "c:\\acad-lib\\civil\\civil\\f" pause 1 1 pause pt3 ""
            "insert" "c:\\acad-lib\\civil\\civil\\c" pause 1 1 pause pt2 "")
         )
(defun c:df11 ()
   (setq pt1 (getpoint "\n insertion point"))
   (setq pt2 (getint "\n no. of colum   :  "))
   (setq pt3 (getint "\n no. of foot    :  "))
   (command "insert" "c:\\acad-lib\\civil\\civil\\df11" pt1 1 1 pause ""
            "insert" "c:\\acad-lib\\civil\\civil\\f" pause 1 1 pause pt3 ""
            "insert" "c:\\acad-lib\\civil\\civil\\c" pause 1 1 pause pt2 "")
         )
(defun c:df12 ()
   (setq pt1 (getpoint "\n insertion point"))
   (setq pt2 (getint "\n no. of colum   :  "))
   (setq pt3 (getint "\n no. of foot    :  "))
   (command "insert" "c:\\acad-lib\\civil\\civil\\df12" pt1 1 1 pause ""
            "insert" "c:\\acad-lib\\civil\\civil\\f" pause 1 1 pause pt3 ""
            "insert" "c:\\acad-lib\\civil\\civil\\c" pause 1 1 pause pt2 "")
         )
